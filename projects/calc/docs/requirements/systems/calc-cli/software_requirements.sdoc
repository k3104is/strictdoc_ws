[DOCUMENT]
TITLE: calc CLI ソフトウェア要求仕様
UID: CALC-CLI-SW-REQS
VERSION: 1.2

[GRAMMAR]
ELEMENTS:
- TAG: REQUIREMENT
  FIELDS:
  - TITLE: UID
    TYPE: String
    REQUIRED: True
  - TITLE: STATUS
    TYPE: SingleChoice(draft, approved, deprecated, retired)
    REQUIRED: True
  - TITLE: TAGS
    TYPE: String
    REQUIRED: True
  - TITLE: PRIORITY
    TYPE: SingleChoice(high, medium, low)
    REQUIRED: True
  - TITLE: TITLE
    TYPE: String
    REQUIRED: True
  - TITLE: STATEMENT
    TYPE: String
    REQUIRED: True
  - TITLE: RATIONALE
    TYPE: String
    REQUIRED: True
  - TITLE: COMMENT
    TYPE: String
    REQUIRED: True
  RELATIONS:
  - TYPE: Parent
  - TYPE: File

[REQUIREMENT]
UID: CALC-FUNC-001
STATUS: approved
TAGS: software-requirement
PRIORITY: high
TITLE: ソフトウェア要求：四則演算
STATEMENT: calcコマンドは、第1引数の演算子としてadd、sub、mul、divのいずれかを、第2引数と第3引数として2つのオペランドを受け取り、指定された演算を実行できなければならない。
RATIONALE: システム要求CALC-SYS-FUNC-001を、calcコマンドが解釈する演算子とオペランドの仕様として実装可能な粒度へ具体化するため。
COMMENT: 検証方法：GoogleTestのCalculatorTest.SupportsAllOperationsを実行し、add、sub、mul、divの演算結果が期待値と一致することを確認する。
RELATIONS:
- TYPE: Parent
  VALUE: CALC-SYS-FUNC-001

[REQUIREMENT]
UID: CALC-FUNC-002
STATUS: approved
TAGS: software-requirement
PRIORITY: high
TITLE: ソフトウェア要求：結果の出力
STATEMENT: 計算に成功した場合、calcコマンドは数値結果と改行を標準出力へ出力し、終了コード0で終了しなければならない。
RATIONALE: システム要求CALC-SYS-FUNC-002を、CLIから観測可能な標準出力と終了コードの契約として具体化するため。
COMMENT: 検証方法：GoogleTestのCliTest.PrintsCalculationResultを実行し、標準出力が期待する数値と改行に一致し、終了コードが0であることを確認する。
RELATIONS:
- TYPE: Parent
  VALUE: CALC-SYS-FUNC-002

[REQUIREMENT]
UID: CALC-ERR-001
STATUS: approved
TAGS: software-requirement
PRIORITY: high
TITLE: ソフトウェア要求：コマンドライン引数の検証
STATEMENT: calcコマンドは、引数の個数が3でない場合、演算子がadd、sub、mul、divのいずれでもない場合、またはオペランドが完全な有限数として解釈できない場合に入力を拒否し、説明メッセージを標準エラー出力へ出力して、非0の終了コードで終了しなければならない。
RATIONALE: システム要求CALC-SYS-ERR-001を満たし、曖昧または非有限な入力が演算処理へ渡されることを防ぐため。
COMMENT: 検証方法：GoogleTestのCliTest.RejectsWrongArgumentCount、CliTest.RejectsUnknownOperation、およびCliTest.RejectsInvalidOperandsを実行し、標準エラー出力と非0の終了コードを確認する。
RELATIONS:
- TYPE: Parent
  VALUE: CALC-SYS-ERR-001

[REQUIREMENT]
UID: CALC-ERR-002
STATUS: approved
TAGS: software-requirement
PRIORITY: high
TITLE: ソフトウェア要求：ゼロ除算
STATEMENT: calcコマンドは、正または負のゼロによる除算を拒否し、説明メッセージを標準エラー出力へ出力して、非0の終了コードで終了しなければならない。
RATIONALE: システム要求CALC-SYS-ERR-002を満たし、符号にかかわらずゼロを除数とする未定義の演算を拒否するため。
COMMENT: 検証方法：GoogleTestのCalculatorTest.RejectsDivisionByZeroおよびCliTest.ReportsDivisionByZeroを実行し、正負のゼロ除算が拒否され、説明メッセージと非0の終了コードが得られることを確認する。
RELATIONS:
- TYPE: Parent
  VALUE: CALC-SYS-ERR-002

[REQUIREMENT]
UID: CALC-ERR-003
STATUS: approved
TAGS: software-requirement
PRIORITY: high
TITLE: ソフトウェア要求：非有限な演算結果
STATEMENT: calcコマンドは、演算結果が有限数でない場合に計算を拒否し、説明メッセージを標準エラー出力へ出力して、非0の終了コードで終了しなければならない。
RATIONALE: システム要求CALC-SYS-ERR-002を満たし、利用可能な有限数の範囲を超えた結果を正常値として出力しないため。
COMMENT: 検証方法：GoogleTestのCliTest.RejectsOverflowingResultを実行し、非有限となる演算結果が拒否され、説明メッセージと非0の終了コードが得られることを確認する。
RELATIONS:
- TYPE: Parent
  VALUE: CALC-SYS-ERR-002

[REQUIREMENT]
UID: CALC-LOG-001
STATUS: approved
TAGS: software-requirement
PRIORITY: medium
TITLE: ソフトウェア要求：日付別ログファイルへの追記
STATEMENT: calcコマンドは、実行環境のローカル日付を使用して実行日のログをlog/YYYY-MM-DD.logへ記録し、対象日のファイルが存在しない場合は自動生成し、存在する場合は既存内容を保持して新しいログを追記しなければならない。
RATIONALE: システム要求CALC-SYS-LOG-001を、日付単位で継続的に保存できるファイル構成として具体化するため。
COMMENT: 検証方法：CLI試験で同じ日に複数の計算を実行し、log/YYYY-MM-DD.logが自動生成され、既存記録を保持したまま実行回数分の記録が追記されることを確認する。
RELATIONS:
- TYPE: Parent
  VALUE: CALC-SYS-LOG-001

[REQUIREMENT]
UID: CALC-LOG-002
STATUS: approved
TAGS: software-requirement
PRIORITY: medium
TITLE: ソフトウェア要求：計算ログの記録形式
STATEMENT: calcコマンドは、正常時には「HH:MM:SS | <左辺> <演算子記号> <右辺> | <結果>」、異常時には「HH:MM:SS | ERROR | <異常内容>」の形式で、1回の計算につき1行を実行日のログファイルへ記録しなければならない。演算子記号はaddを+、subを-、mulを*、divを/として記録しなければならない。
RATIONALE: システム要求CALC-SYS-LOG-001で必要な正常時と異常時の情報を、ログレコードとして具体化するため。
COMMENT: 検証方法：CLI試験でadd、sub、mul、divの正常な計算、入力異常、および計算異常を実行し、正常ログと異常ログが規定の区切り、HH:MM:SS、演算子記号、および1計算1行の形式に一致することを確認する。
RELATIONS:
- TYPE: Parent
  VALUE: CALC-SYS-LOG-001

[REQUIREMENT]
UID: CALC-LOG-003
STATUS: approved
TAGS: software-requirement
PRIORITY: medium
TITLE: ソフトウェア要求：計算ログの読み込みと出力
STATEMENT: calcコマンドは、「calc log YYYY-MM-DD」が実行された場合、log/YYYY-MM-DD.logを読み込み、その内容を標準出力へ出力しなければならない。
RATIONALE: システム要求CALC-SYS-LOG-002を、日付別ログファイルの読み込みとCLI出力として具体化するため。
COMMENT: 検証方法：CLI試験で正常および異常な計算のログを作成した後にログ提示を要求し、日付別ログファイルの内容と出力内容が一致することを確認する。
RELATIONS:
- TYPE: Parent
  VALUE: CALC-SYS-LOG-002

[REQUIREMENT]
UID: CALC-LOG-004
STATUS: approved
TAGS: software-requirement
PRIORITY: medium
TITLE: ソフトウェア要求：ログ入出力失敗の通知
STATEMENT: calcコマンドは、logディレクトリが存在しない場合またはログファイルの読み書きに失敗した場合、異常内容を標準出力へ出力して非0で終了しなければならない。ログ書き込みに失敗した場合は計算結果を標準出力へ出力してはならない。
RATIONALE: システム要求CALC-SYS-LOG-003を、ログファイル入出力失敗時のCLI出力として具体化するため。
COMMENT: 検証方法：CLI試験でlogディレクトリの不存在、書き込み不能なログファイル、および「calc log YYYY-MM-DD」による読み込み失敗を発生させ、異常内容が標準出力へ出力され、計算結果が出力されず、終了コードが非0であることを確認する。
RELATIONS:
- TYPE: Parent
  VALUE: CALC-SYS-LOG-003
