[DOCUMENT]
TITLE: calc CLI システム要求仕様
UID: CALC-CLI-SYS-REQS
VERSION: 1.5

[GRAMMAR]
ELEMENTS:
- TAG: REQUIREMENT
  FIELDS:
  - TITLE: UID
    TYPE: String
    REQUIRED: True
  - TITLE: STATUS
    TYPE: SingleChoice(draft, approved, deprecated, retired)
    REQUIRED: True
  - TITLE: TAGS
    TYPE: String
    REQUIRED: True
  - TITLE: PRIORITY
    TYPE: SingleChoice(high, medium, low)
    REQUIRED: True
  - TITLE: TITLE
    TYPE: String
    REQUIRED: True
  - TITLE: STATEMENT
    TYPE: String
    REQUIRED: True
  - TITLE: RATIONALE
    TYPE: String
    REQUIRED: True
  - TITLE: COMMENT
    TYPE: String
    REQUIRED: True
  RELATIONS:
  - TYPE: Parent
  - TYPE: File

[REQUIREMENT]
UID: CALC-SYS-FUNC-001
STATUS: approved
TAGS: system-requirement
PRIORITY: high
TITLE: システム要求：四則演算機能
STATEMENT: システムは、演算子と2つのオペランドをコマンドライン引数として受け取り、加算、減算、乗算、および除算を実行しなければならない。
RATIONALE: 利害関係者要求CALC-STK-004の四則演算を、calc CLIシステムの外部機能として具体化するため。
COMMENT: 検証方法：システム試験でadd、sub、mul、divに正負および小数のオペランドを与え、指定した各演算の期待値と一致することを確認する。
RELATIONS:
- TYPE: Parent
  VALUE: CALC-STK-004

[REQUIREMENT]
UID: CALC-SYS-FUNC-002
STATUS: approved
TAGS: system-requirement
PRIORITY: high
TITLE: システム要求：計算結果の提示
STATEMENT: システムは、計算に成功した場合に数値結果を利用者へ提示し、成功を示して終了しなければならない。
RATIONALE: 利害関係者要求CALC-STK-004を満たし、計算の成否と結果をCLI利用者が判定できるようにするため。
COMMENT: 検証方法：システム試験で正常な計算を実行し、数値結果が標準出力へ出力され、終了コードが0であることを確認する。
RELATIONS:
- TYPE: Parent
  VALUE: CALC-STK-004

[REQUIREMENT]
UID: CALC-SYS-ERR-001
STATUS: approved
TAGS: system-requirement
PRIORITY: high
TITLE: システム要求：入力異常の通知
STATEMENT: システムは、コマンドライン引数が処理できない場合に計算を実行せず、理由を利用者へ通知し、失敗を示して終了しなければならない。
RATIONALE: 利害関係者要求CALC-STK-004を満たし、処理不能な入力に対して利用者が修正可能な情報を提供するため。
COMMENT: 検証方法：システム試験で引数不足、未対応演算子、および不正なオペランドを与え、計算結果が出力されず、理由が標準エラー出力へ出力され、終了コードが非0であることを確認する。
RELATIONS:
- TYPE: Parent
  VALUE: CALC-STK-004

[REQUIREMENT]
UID: CALC-SYS-ERR-002
STATUS: approved
TAGS: system-requirement
PRIORITY: high
TITLE: システム要求：計算異常の通知
STATEMENT: システムは、指定された演算を有限な数値結果として完了できない場合に結果を提示せず、理由を利用者へ通知し、失敗を示して終了しなければならない。
RATIONALE: 利害関係者要求CALC-STK-004を満たし、無効な計算結果を正常な結果として利用者へ提示しないため。
COMMENT: 検証方法：システム試験でゼロ除算および結果のオーバーフローを発生させ、計算結果が出力されず、理由が標準エラー出力へ出力され、終了コードが非0であることを確認する。
RELATIONS:
- TYPE: Parent
  VALUE: CALC-STK-004

[REQUIREMENT]
UID: CALC-SYS-LOG-001
STATUS: approved
TAGS: system-requirement
PRIORITY: medium
TITLE: システム要求：計算ログの記録
STATEMENT: システムは、計算要求ごとに実行環境のローカル時刻を使用し、正常時は時刻、計算内容、および計算結果を、異常時は時刻、ERROR、および異常内容を1行の計算ログとして記録しなければならない。
RATIONALE: CALC-STK-005を満たすため、計算後の調査に必要な実行状況と失敗原因を残す必要がある。
COMMENT: 検証方法：システム試験で正常な計算、入力異常、および計算異常を発生させ、正常時はHH:MM:SS、計算内容、計算結果が、異常時はHH:MM:SS、ERROR、異常内容が各1行で計算ログに記録されることを確認する。
RELATIONS:
- TYPE: Parent
  VALUE: CALC-STK-005

[REQUIREMENT]
UID: CALC-SYS-LOG-002
STATUS: approved
TAGS: system-requirement
PRIORITY: medium
TITLE: システム要求：計算ログの提示
STATEMENT: システムは、運用担当者から日付を指定して要求された場合に、指定日の計算ログを標準出力へ提示しなければならない。
RATIONALE: CALC-STK-005を満たすため、記録された情報を運用担当者が確認できる必要がある。
COMMENT: 検証方法：システム試験で複数の正常および失敗する計算を実行した後に計算ログの提示を要求し、記録された各計算の実行状況と失敗理由を確認できることを確認する。
RELATIONS:
- TYPE: Parent
  VALUE: CALC-STK-005

[REQUIREMENT]
UID: CALC-SYS-LOG-003
STATUS: approved
TAGS: system-requirement
PRIORITY: medium
TITLE: システム要求：ログ入出力異常の通知
STATEMENT: システムは、logディレクトリが存在しない場合または計算ログの読み書きに失敗した場合、その異常内容を標準出力へ通知して非0で終了しなければならない。ログ書き込みに失敗した場合は計算結果を出力してはならない。
RATIONALE: ログを記録または提示できない状態を利用者または運用担当者が把握できるようにするため。
COMMENT: 検証方法：システム試験でlogディレクトリの不存在、書き込み失敗、および読み込み失敗を発生させ、異常内容が標準出力へ出力され、計算結果が出力されず、終了コードが非0であることを確認する。
RELATIONS:
- TYPE: Parent
  VALUE: CALC-STK-005
